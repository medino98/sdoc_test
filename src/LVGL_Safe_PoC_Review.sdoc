[DOCUMENT]
TITLE: LVGL Safe PoC Review Records
UID: LVGL-SAFE-POC-REVIEW-RECORDS
VERSION: 0.2
METADATA:
  LAST_MODIFIED: 2026-08-10

[GRAMMAR]
IMPORT_FROM_FILE: grammar.sgra

[[REVIEW_RECORD]]
UID: REVIEW-R1
TITLE: R1 - Software Unit Implementation Review (2026-08-05)
REVIEW_TYPE: Software Unit Implementation Review
METHOD: 4-Eye
REVIEW_DATE: 2026-08-05
DECISION: To-be-released-after-rework
STATEMENT: >>>
Review record for the LVGL Safe PoC component, replacing the xls
"Review Information" tab. Fields are enum-constrained by the grammar
instead of Excel data-validation dropdowns, so an invalid value is a
parse error, not a silently-accepted typo.
<<<
DOCUMENT_UNDER_REVIEW: >>>
\path\to\File A
\path\to\File B
Polarion-12345
<<<

[[SECTION]]
TITLE: Participants

[PARTICIPANT]
UID: REVIEW-R1-PARTICIPANT-001
NAME: Firstname SURNAME
PROJECT_ROLE: Reviewer
PRESENCE_STATUS: M

[PARTICIPANT]
UID: REVIEW-R1-PARTICIPANT-002
NAME: Firstname SURNAME
PROJECT_ROLE: Author
PRESENCE_STATUS: M

[[/SECTION]]

[[SECTION]]
TITLE: Review Protocol

[FINDING]
UID: REVIEW-R1-FINDING-001
IDENTIFIER: file A line 69
SEVERITY: Suggestion
FINDING_STATUS: Open
DONE_BY: Firstname SURNAME
FINDING_DATE: 2026-08-05
STATEMENT: It could be done a more sophisticated way...

[FINDING]
UID: REVIEW-R1-FINDING-002
IDENTIFIER: file A
SEVERITY: Minor
FINDING_STATUS: Closed
DONE_BY: Firstname SURNAME
FINDING_DATE: 2026-08-05
STATEMENT: Example finding: required controlled evidence or rationale is missing.
REWORK_COMMENT: It is fixed!

[FINDING]
UID: REVIEW-R1-FINDING-003
IDENTIFIER: file B
SEVERITY: Major
FINDING_STATUS: Closed
DONE_BY: Firstname SURNAME
FINDING_DATE: 2026-08-05
STATEMENT: Example finding: the reviewed work product does not conform to an applicable requirement or guideline.
REWORK_COMMENT: It is fixed!

[FINDING]
UID: REVIEW-R1-FINDING-004
IDENTIFIER: Polarion-12345
SEVERITY: Major
FINDING_STATUS: Open
DONE_BY: Firstname SURNAME
FINDING_DATE: 2026-08-05
STATEMENT: Example finding: the Polarion item is not linked to its required requirement, design, code, or verification evidence.

[[/SECTION]]

[[/REVIEW_RECORD]]

[[REVIEW_RECORD]]
UID: REVIEW-PR1
TITLE: RN - <Review type> (<YYYY-MM-DD>)
REVIEW_TYPE: Generic Document Review
METHOD: 4-Eye
REVIEW_DATE: 2026-08-11
DECISION: Not-to-be-released-successive-review-required
STATEMENT: >>>
<Scope and purpose of this review: what was reviewed, against which
baseline, and anything a later reader needs to interpret the decision.>
<<<
DOCUMENT_UNDER_REVIEW: >>>
review_templates/Review_Record_TEMPLATE.sdoc
src/test.txt
<<<

[[SECTION]]
TITLE: Participants

[PARTICIPANT]
UID: REVIEW-PR1-PARTICIPANT-001
NAME: <Firstname SURNAME>
PROJECT_ROLE: Reviewer
PRESENCE_STATUS: M

[[/SECTION]]

[[SECTION]]
TITLE: Review Protocol

[FINDING]
UID: REVIEW-PR1-FINDING-001
IDENTIFIER: <file / line / Polarion item the finding is against>
SEVERITY: Minor
FINDING_STATUS: Open
DONE_BY: <Firstname SURNAME>
FINDING_DATE: <YYYY-MM-DD>
STATEMENT: <What is wrong, and why it is wrong.>

[[/SECTION]]

[[/REVIEW_RECORD]]
