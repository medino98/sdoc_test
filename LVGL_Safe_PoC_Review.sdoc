[DOCUMENT]
TITLE: LVGL Safe PoC Review
UID: LVGL-SAFE-POC-REVIEW-001
VERSION: 0.1
DATE: 2026-08-05

[GRAMMAR]
IMPORT_FROM_FILE: grammar.sgra

[REVIEW_META]
UID: REVIEW-META-001
REVIEW_TYPE: Software Unit Implementation Review
METHOD: 4-Eye
REVIEW_DATE: 2026-08-05
DECISION: To-be-released-after-rework
TITLE: LVGL Safe PoC Review
STATEMENT: >>>
Review record for the LVGL Safe PoC component, replacing the xls
"Review Information" tab. Fields are enum-constrained by the grammar
instead of Excel data-validation dropdowns, so an invalid value is a
parse error, not a silently-accepted typo. Something else, here just to
stir things up.
<<<
DOCUMENT_UNDER_REVIEW: >>>
\path\to\File A
\path\to\File B
Polarion-12345
<<<

[[SECTION]]
TITLE: Participants

[PARTICIPANT]
NAME: Firstname SURNAME
PROJECT_ROLE: Reviewer
REQUIREMENT_LEVEL: M

[PARTICIPANT]
NAME: Firstname SURNAME
PROJECT_ROLE: Author
REQUIREMENT_LEVEL: M

[[/SECTION]]

[[SECTION]]
TITLE: Review Protocol

[FINDING]
UID: FINDING-001
IDENTIFIER: file A line 69
SEVERITY: Suggestion
FINDING_STATUS: Open
DONE_BY: Firstname SURENAME
FINDING_DATE: 2026-08-05
STATEMENT: It could be done a more sophisticated way...

[FINDING]
UID: FINDING-002
IDENTIFIER: file A
SEVERITY: Minor
FINDING_STATUS: Closed
DONE_BY: Firstname SURENAME
FINDING_DATE: 2026-08-05
STATEMENT: Example finding: required controlled evidence or rationale is missing.
REWORK_COMMENT: It is fixed!

[FINDING]
UID: FINDING-003
IDENTIFIER: file B
SEVERITY: Major
FINDING_STATUS: Closed
DONE_BY: Firstname SURENAME
FINDING_DATE: 2026-08-05
STATEMENT: Example finding: the reviewed work product does not conform to an applicable requirement or guideline.
REWORK_COMMENT: It is fixed!

[FINDING]
UID: FINDING-004
IDENTIFIER: Polarion-12345
SEVERITY: Major
FINDING_STATUS: Open
DONE_BY: Firstname SURENAME
FINDING_DATE: 2026-08-05
STATEMENT: Example finding: the Polarion item is not linked to its required requirement, design, code, or verification evidence.

[[/SECTION]]
