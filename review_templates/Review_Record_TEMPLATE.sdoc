[DOCUMENT]
TITLE: Review Record TEMPLATE
UID: REVIEW-RECORD-TEMPLATE
VERSION: 0.2
METADATA:
  LAST_MODIFIED: 2026-08-11

[GRAMMAR]
IMPORT_FROM_FILE: grammar_temp.sgra

[[REVIEW_RECORD]]
UID: REVIEW-RN
TITLE: RN - <Review type> (<YYYY-MM-DD>)
REVIEW_TYPE: Generic Document Review
METHOD: 4-Eye
REVIEW_DATE: <YYYY-MM-DD>
DECISION: Not-to-be-released-successive-review-required
STATEMENT: >>>
<Scope and purpose of this review: what was reviewed, against which
baseline, and anything a later reader needs to interpret the decision.>
<<<
DOCUMENT_UNDER_REVIEW: >>>
<\path\to\File A>
<\path\to\File B>
<Polarion-NNNNN>
<<<

[[SECTION]]
TITLE: Participants

[PARTICIPANT]
UID: REVIEW-RN-PARTICIPANT-001
NAME: <Firstname SURNAME>
PROJECT_ROLE: Reviewer
PRESENCE_STATUS: M

[[/SECTION]]

[[SECTION]]
TITLE: Review Protocol

[FINDING]
UID: REVIEW-RN-FINDING-001
IDENTIFIER: <file / line / Polarion item the finding is against>
SEVERITY: Minor
FINDING_STATUS: Open
DONE_BY: <Firstname SURNAME>
FINDING_DATE: <YYYY-MM-DD>
STATEMENT: <What is wrong, and why it is wrong.>

[[/SECTION]]

[[/REVIEW_RECORD]]
