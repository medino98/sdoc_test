[DOCUMENT]
TITLE: C Coding Guideline Review
UID: C-CODING-GUIDELINE-REVIEW
VERSION: 1.0
METADATA:
  LAST_MODIFIED: 2026-09-24

[GRAMMAR]
IMPORT_FROM_FILE: grammar.sgra

[[REVIEW_RECORD]]
UID: GL_302-REVIEW-R1
TITLE: R1 - Walkthrough (2026-09-24)
REVIEW_TYPE: Generic Document Review
METHOD: Walkthrough
REVIEW_DATE: 2026-09-24
DECISION: To-be-released
STATEMENT: >>>
After mutual consideration, the document had no known or found issues.
<<<
DOCUMENT_UNDER_REVIEW: >>>
https://internal.lvgl.io/polarion/#/project/lvglsafe/wiki/Guidelines/GL_302?revision=1601
<<<

[[SECTION]]
TITLE: Participants

[PARTICIPANT]
UID: REVIEW-R1-PARTICIPANT-001
NAME: Máté GULYÁS
PROJECT_ROLE: Reviewer
PRESENCE_STATUS: M

[PARTICIPANT]
UID: REVIEW-R1-PARTICIPANT-002
NAME: Péter TARJÁN
PROJECT_ROLE: Reviewer
PRESENCE_STATUS: M

[[/SECTION]]

[[SECTION]]
TITLE: Review Protocol

[FINDING]
UID: REVIEW-RN-FINDING-001
IDENTIFIER: <file / line / Polarion item the finding is against>
SEVERITY: Minor
FINDING_STATUS: Open
DONE_BY: <Firstname SURNAME>
FINDING_DATE: <YYYY-MM-DD>
STATEMENT: >>>
Okay, no problem.
<<<

[[/SECTION]]

[[/REVIEW_RECORD]]
