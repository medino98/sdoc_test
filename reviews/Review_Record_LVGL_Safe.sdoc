[DOCUMENT]
TITLE: Review Record LVGL Safe
UID: REVIEW-RECORD-1
VERSION: 0.2
METADATA:
  LAST_MODIFIED: 2026-09-24

[GRAMMAR]
IMPORT_FROM_FILE: grammar.sgra

[[REVIEW_RECORD]]
UID: REVIEW-PR3
TITLE: RN - SUIR (2026-08-11)
REVIEW_TYPE: Software Unit Implementation Review
METHOD: 4-Eye
REVIEW_DATE: 2026-08-11
DECISION: Not-to-be-released-successive-review-required
STATEMENT: >>>
Test review.
<<<
DOCUMENT_UNDER_REVIEW: >>>
src/test.txt
<<<

[[SECTION]]
TITLE: Participants

[PARTICIPANT]
UID: REVIEW-PR3-PARTICIPANT-001
NAME: Máté Gulyás
PROJECT_ROLE: Reviewer
PRESENCE_STATUS: M

[[/SECTION]]

[[SECTION]]
TITLE: Review Protocol

[FINDING]
UID: REVIEW-PR3-FINDING-001
IDENTIFIER: src/test.txt -> line 1
SEVERITY: Suggestion
FINDING_STATUS: Open
DONE_BY: Gulyás Máté
FINDING_DATE: 2026-08-11
STATEMENT: >>>
Just a test.
<<<

[[/SECTION]]

[[/REVIEW_RECORD]]

[[REVIEW_RECORD]]
UID: REVIEW-PR5
TITLE: RN - Walktrhough (2026-08-12)
REVIEW_TYPE: Generic Document Review
METHOD: Walkthrough
REVIEW_DATE: 2026-08-12
DECISION: Not-to-be-released-successive-review-required
STATEMENT: >>>
Test with Péter Tarján.
<<<
DOCUMENT_UNDER_REVIEW: >>>
src/test_2.txt
<<<

[[SECTION]]
TITLE: Participants

[PARTICIPANT]
UID: REVIEW-PR5-PARTICIPANT-001
NAME: Máté Gulyás
PROJECT_ROLE: Reviewer
PRESENCE_STATUS: M

[[/SECTION]]

[[SECTION]]
TITLE: Review Protocol

[FINDING]
UID: REVIEW-PR5-FINDING-001
IDENTIFIER: test_2 line 1
SEVERITY: Minor
FINDING_STATUS: Closed
DONE_BY: Máté Gulyás
FINDING_DATE: 2026-08-12
STATEMENT: >>>
Nothing is wrong.
<<<

[[/SECTION]]

[[/REVIEW_RECORD]]
